import FreeCAD
import FreeCADGui
import Part
import Draft
import os
import re
from PySide6 import QtWidgets


PREFIX = "SP_"
GROUP_NAME = "StressProbe"

_panel = None


def find_nearest_node(point, nodes):
    min_dist = float("inf")
    nearest_id = None
    for nid, coord in nodes.items():
        dist = coord.distanceToPoint(point)
        if dist < min_dist:
            min_dist = dist
            nearest_id = nid
    return nearest_id, min_dist


def get_point_from_selection():
    sel = FreeCADGui.Selection.getSelectionEx()
    if not sel:
        return None
    for s in sel:
        for sub in s.SubElementNames:
            if "Vertex" in sub:
                vi = int(sub.replace("Vertex", "")) - 1
                if vi < len(s.Object.Shape.Vertexes):
                    return s.Object.Shape.Vertexes[vi].Point
            elif "Face" in sub:
                fi = int(sub.replace("Face", "")) - 1
                if fi < len(s.Object.Shape.Faces):
                    return s.Object.Shape.Faces[fi].CenterOfGravity
            elif "Edge" in sub:
                ei = int(sub.replace("Edge", "")) - 1
                if ei < len(s.Object.Shape.Edges):
                    return s.Object.Shape.Edges[ei].CenterOfGravity
    return None


def get_fem_result():
    doc = FreeCAD.ActiveDocument
    if doc is None:
        return None
    for obj in doc.Objects:
        if obj.TypeId in ("Fem::FemResultObject", "Fem::FemResultObjectPython"):
            return obj
    return None


def get_fem_analysis():
    doc = FreeCAD.ActiveDocument
    if doc is None:
        return None
    for obj in doc.Objects:
        if obj.TypeId in ("Fem::AnalysisPython", "Fem::Analysis"):
            return obj
    return None


def get_reaction_forces():
    temp = os.path.expandvars(r"%TEMP%")
    dirs = sorted(
        [d for d in os.listdir(temp) if d.startswith("fcfem_")],
        key=lambda d: os.path.getmtime(os.path.join(temp, d)),
        reverse=True
    )
    if not dirs:
        return None

    dat_path = os.path.join(temp, dirs[0], "FEMMeshNetgen.dat")
    if not os.path.exists(dat_path):
        return None

    with open(dat_path, "r") as f:
        text = f.read()

    pattern = r'total force \(fx,fy,fz\) for set (\S+) and time\s+([\d.E+-]+)\s*\n\s+([-\d.E+]+)\s+([-\d.E+]+)\s+([-\d.E+]+)'
    matches = re.findall(pattern, text)

    results = []
    for setName, time_val, fx_str, fy_str, fz_str in matches:
        fx = float(fx_str)
        fy = float(fy_str)
        fz = float(fz_str)
        total = (fx**2 + fy**2 + fz**2)**0.5
        results.append({
            "set": setName,
            "time": float(time_val),
            "fx": fx,
            "fy": fy,
            "fz": fz,
            "total": total,
        })
    return results


def get_reaction_forces_text():
    rf_data = get_reaction_forces()
    if not rf_data:
        return "\n=== REACTION FORCES ===\n  No reaction force data found.\n"

    lines = ["\n=== REACTION FORCES ==="]
    lines.append("  {:<12s} {:>12s} {:>12s} {:>12s} {:>12s}".format(
        "Constraint", "Fx (N)", "Fy (N)", "Fz (N)", "Total (N)"))
    for rf in rf_data:
        lines.append("  {:<12s} {:>12.2f} {:>12.2f} {:>12.2f} {:>12.2f}".format(
            rf["set"], rf["fx"], rf["fy"], rf["fz"], rf["total"]))
    return "\n".join(lines) + "\n"


def get_conditions_text():
    doc = FreeCAD.ActiveDocument
    if doc is None:
        return "No active document\n"
    lines = []
    lines.append("BOUNDARY CONDITIONS:")
    lines.append("-" * 40)
    found = False

    for obj in doc.Objects:
        tid = obj.TypeId
        name = obj.Label

        if "ConstraintFixed" in tid:
            refs = []
            try:
                for r in obj.References:
                    refs.append("{}:{}".format(r[0], r[1]))
            except Exception:
                pass
            lines.append("  Fixed: {} [{}]".format(name, ", ".join(refs) if refs else "N/A"))
            found = True

        elif "ConstraintForce" in tid:
            fval = "N/A"
            try:
                fval = "{:.4f} N".format(obj.Force)
            except Exception:
                try:
                    fval = "{} N".format(obj.Force)
                except Exception:
                    pass
            fdir = ""
            try:
                fdir = " dir=({:.4f}, {:.4f}, {:.4f})".format(
                    obj.Direction.x, obj.Direction.y, obj.Direction.z)
            except Exception:
                pass
            rev = ""
            try:
                rev = " reversed" if obj.Reversed else ""
            except Exception:
                pass
            refs = []
            try:
                for r in obj.References:
                    refs.append("{}:{}".format(r[0], r[1]))
            except Exception:
                pass
            lines.append("  Force: {} = {} {}{} [{}]".format(name, fval, fdir, rev,
                ", ".join(refs) if refs else "N/A"))
            found = True

        elif "ConstraintPressure" in tid:
            pval = "N/A"
            try:
                pval = "{:.4f} MPa".format(obj.Pressure)
            except Exception:
                pass
            refs = []
            try:
                for r in obj.References:
                    refs.append("{}:{}".format(r[0], r[1]))
            except Exception:
                pass
            lines.append("  Pressure: {} = {} [{}]".format(name, pval,
                ", ".join(refs) if refs else "N/A"))
            found = True

        elif "ConstraintDisplacement" in tid:
            refs = []
            try:
                for r in obj.References:
                    refs.append("{}:{}".format(r[0], r[1]))
            except Exception:
                pass
            lines.append("  Displacement: {} [{}]".format(name, ", ".join(refs) if refs else "N/A"))
            found = True

        elif "ConstraintTemperature" in tid:
            tval = "N/A"
            try:
                tval = "{:.4f} C".format(obj.Temperature)
            except Exception:
                pass
            lines.append("  Temperature: {} = {}".format(name, tval))
            found = True

        elif "ConstraintSelfWeight" in tid:
            lines.append("  Self Weight: {}".format(name))
            found = True

        elif "ConstraintCentrif" in tid:
            lines.append("  Centrifugal: {}".format(name))
            found = True

    for obj in doc.Objects:
        if obj.TypeId in ("Fem::MaterialCommon", "Fem::Material"):
            try:
                mat = obj.Material
                lines.append("")
                lines.append("MATERIAL:")
                lines.append("-" * 40)
                for k, v in mat.items():
                    if v and k != "Name":
                        lines.append("  {}: {}".format(k, v))
            except Exception:
                pass

    if not found:
        lines.append("  (none found)")

    return "\n".join(lines)


def next_condition_number():
    doc = FreeCAD.ActiveDocument
    if doc is None:
        return 1
    max_n = 0
    for obj in doc.Objects:
        if obj.TypeId == "App::DocumentObjectGroup" and obj.Name.startswith(PREFIX + "Condition"):
            try:
                n = int(obj.Name.split("_")[-1])
                if n > max_n:
                    max_n = n
            except Exception:
                pass
    return max_n + 1


def cleanup():
    doc = FreeCAD.ActiveDocument
    if doc is None:
        return 0
    count = 0
    grp = doc.getObject(GROUP_NAME)
    if grp:
        names = [o.Name for o in grp.Group]
        for name in names:
            doc.removeObject(name)
        count = len(names)
        doc.removeObject(GROUP_NAME)
    condition_names = set()
    for obj in doc.Objects:
        if obj.TypeId == "App::DocumentObjectGroup" and obj.Name.startswith(PREFIX + "Condition"):
            for child in obj.Group:
                condition_names.add(child.Name)
    to_remove = [o.Name for o in doc.Objects
                 if o.Name.startswith(PREFIX)
                 and o.Name not in condition_names
                 and not (o.TypeId == "App::DocumentObjectGroup" and o.Name.startswith(PREFIX + "Condition"))]
    for name in to_remove:
        doc.removeObject(name)
    count += len(to_remove)
    if count:
        doc.recompute()
    return count


def cleanup_old():
    doc = FreeCAD.ActiveDocument
    if doc is None:
        return 0
    condition_names = set()
    for obj in doc.Objects:
        if obj.TypeId == "App::DocumentObjectGroup" and "Condition" in obj.Name:
            for child in obj.Group:
                condition_names.add(child.Name)
    to_remove = [o.Name for o in doc.Objects
                 if (o.Name.startswith("StressProbe") or o.Name.startswith("StressLeader"))
                 and o.Name not in condition_names
                 and not (o.TypeId == "App::DocumentObjectGroup" and "Condition" in o.Name)]
    for name in to_remove:
        doc.removeObject(name)
    if to_remove:
        doc.recompute()
    return len(to_remove)


def get_or_create_group():
    doc = FreeCAD.ActiveDocument
    grp = doc.getObject(GROUP_NAME)
    if grp is None:
        grp = doc.addObject("App::DocumentObjectGroup", GROUP_NAME)
    return grp


def make_marker(point, label, size=0.4, color=None):
    doc = FreeCAD.ActiveDocument
    sphere = doc.addObject("Part::Sphere", label)
    sphere.Radius = size
    sphere.Placement.Base = point
    if color is not None:
        try:
            sphere.ViewObject.ShapeColor = color
        except Exception:
            pass
    grp = get_or_create_group()
    grp.addObject(sphere)
    return sphere


def make_text_label(point, lines, label, color=None, offset=(2.0, 1.5, 0.0)):
    doc = FreeCAD.ActiveDocument
    text_point = FreeCAD.Vector(point.x + offset[0], point.y + offset[1], point.z + offset[2])
    pl = FreeCAD.Placement()
    pl.Base = text_point
    txt = Draft.make_text(lines, placement=pl, screen=False, height=3.0)
    txt.Label = label
    if color is not None:
        try:
            txt.ViewObject.TextColor = color
        except Exception:
            pass
    leader = doc.addObject("Part::Feature", label + "_leader")
    leader.Shape = Part.makeLine(point, text_point)
    if color is not None:
        try:
            leader.ViewObject.LineColor = color
        except Exception:
            pass
    grp = get_or_create_group()
    grp.addObject(txt)
    grp.addObject(leader)
    return txt


def _run_probe():
    global _panel

    doc = FreeCAD.ActiveDocument
    if doc is None:
        return

    result = get_fem_result()
    if result is None:
        return

    point = get_point_from_selection()

    nodes = result.Mesh.FemMesh.Nodes
    node_numbers = result.NodeNumbers

    vm_arr = list(result.vonMises)
    smax_arr = list(result.PrincipalMax)
    smin_arr = list(result.PrincipalMin)
    mshear_arr = list(result.MaxShear)
    disp_arr = list(result.DisplacementLengths)

    max_vm_idx = vm_arr.index(max(vm_arr))
    min_vm_idx = vm_arr.index(min(vm_arr))
    max_disp_idx = disp_arr.index(max(disp_arr))
    min_disp_idx = disp_arr.index(min(disp_arr))

    cleanup()
    cleanup_old()

    if _panel is not None:
        offset = (_panel.spin_x.value(), _panel.spin_y.value(), _panel.spin_z.value())
    else:
        offset = (2.0, 1.5, 0.0)
    red = (1.0, 0.0, 0.0, 1.0)
    blue = (0.0, 0.0, 1.0, 1.0)
    green = (0.0, 0.7, 0.0, 1.0)

    max_vm_coord = nodes[node_numbers[max_vm_idx]]
    make_marker(max_vm_coord, PREFIX + "MaxVM", color=red)
    make_text_label(max_vm_coord, [
        "MAX vonMises {:.3f} MPa".format(max(vm_arr)),
        "Node {}".format(node_numbers[max_vm_idx]),
    ], PREFIX + "MaxVMText", color=red, offset=offset)

    min_vm_coord = nodes[node_numbers[min_vm_idx]]
    make_marker(min_vm_coord, PREFIX + "MinVM", color=blue)
    make_text_label(min_vm_coord, [
        "MIN vonMises {:.3f} MPa".format(min(vm_arr)),
        "Node {}".format(node_numbers[min_vm_idx]),
    ], PREFIX + "MinVMText", color=blue, offset=offset)

    max_disp_coord = nodes[node_numbers[max_disp_idx]]
    make_marker(max_disp_coord, PREFIX + "MaxDisp", color=red)
    make_text_label(max_disp_coord, [
        "MAX Disp {:.6f} mm".format(max(disp_arr)),
        "Node {}".format(node_numbers[max_disp_idx]),
    ], PREFIX + "MaxDispText", color=red, offset=offset)

    min_disp_coord = nodes[node_numbers[min_disp_idx]]
    make_marker(min_disp_coord, PREFIX + "MinDisp", color=blue)
    make_text_label(min_disp_coord, [
        "MIN Disp {:.6f} mm".format(min(disp_arr)),
        "Node {}".format(node_numbers[min_disp_idx]),
    ], PREFIX + "MinDispText", color=blue, offset=offset)

    text_lines = (
        "=== BODY MAX / MIN ===\n"
        "                    MAX              MIN\n"
        "  von Mises:  {:>10.4f} MPa  {:>10.4f} MPa\n"
        "  Sig1:       {:>10.4f} MPa  {:>10.4f} MPa\n"
        "  Sig3:       {:>10.4f} MPa  {:>10.4f} MPa\n"
        "  Max Shear:  {:>10.4f} MPa  {:>10.4f} MPa\n"
        "  Disp:       {:>10.6f} mm   {:>10.6f} mm\n"
        "\n"
        "  Total nodes: {}"
        "{}\n".format(
            max(vm_arr), min(vm_arr),
            max(smax_arr), min(smax_arr),
            max(smin_arr), min(smin_arr),
            max(mshear_arr), min(mshear_arr),
            max(disp_arr), min(disp_arr),
            len(node_numbers),
            get_reaction_forces_text(),
        )
    )

    if point is not None:
        index_map = {num: i for i, num in enumerate(node_numbers)}
        nearest_id, min_dist = find_nearest_node(point, nodes)
        idx = index_map[nearest_id]
        coord = nodes[nearest_id]

        vm = result.vonMises[idx]
        smax = result.PrincipalMax[idx]
        smin = result.PrincipalMin[idx]
        mshear = result.MaxShear[idx]
        disp = result.DisplacementLengths[idx]

        make_marker(coord, PREFIX + "Probe", color=green)
        make_text_label(coord, [
            "Node {}".format(nearest_id),
            "vonMises: {:.3f} MPa".format(vm),
            "Sig1: {:.3f} MPa".format(smax),
            "Sig3: {:.3f} MPa".format(smin),
            "MaxShear: {:.3f} MPa".format(mshear),
            "Disp: {:.6f} mm".format(disp),
        ], PREFIX + "ProbeText", color=green, offset=offset)

        probe_text = (
            "=== PROBED POINT ===\n"
            "  Node:         {}  (dist: {:.4f} mm)\n"
            "  Position:     ({:.4f}, {:.4f}, {:.4f})\n"
            "  von Mises:    {:.4f} MPa\n"
            "  Sig1:         {:.4f} MPa\n"
            "  Sig3:         {:.4f} MPa\n"
            "  Max Shear:    {:.4f} MPa\n"
            "  Displacement: {:.6f} mm\n"
            "\n".format(
                nearest_id, min_dist, coord.x, coord.y, coord.z,
                vm, smax, smin, mshear, disp,
            )
        )
        text_lines = probe_text + text_lines
    else:
        text_lines = "(No selection — showing body max/min only)\n\n" + text_lines

    doc.recompute()

    if _panel is not None:
        _panel.result_text.setPlainText(text_lines)
        if point is not None:
            _panel.status.setText("Probed Node {} | Max VM: {:.3f} | Min VM: {:.3f}".format(
                nearest_id, max(vm_arr), min(vm_arr)))
            _panel.status.setStyleSheet("color: green; font-weight: bold;")
        else:
            _panel.status.setText("Max VM: {:.3f} | Min VM: {:.3f}".format(max(vm_arr), min(vm_arr)))
            _panel.status.setStyleSheet("color: green; font-weight: bold;")


class ProbeCommand:
    def GetResources(self):
        return {"Pixmap": "", "MenuText": "Probe Stress", "ToolTip": "Probe stress at selected vertex (Ctrl+P)"}

    def Activated(self):
        _run_probe()

    def IsActive(self):
        return FreeCAD.ActiveDocument is not None


FreeCADGui.addCommand("StressProbe_Probe", ProbeCommand())

try:
    FreeCADGui.addShortcut("StressProbe_Probe", "Ctrl+P")
except Exception:
    pass


class StressProbeTaskPanel:
    def __init__(self):
        self.form = QtWidgets.QWidget()
        self.form.setWindowTitle("Stress Probe")
        self.form.setMinimumWidth(450)
        self.form.setMinimumHeight(500)

        layout = QtWidgets.QVBoxLayout(self.form)

        self.info = QtWidgets.QLabel(
            "1. Select a vertex, edge, or face\n"
            "2. Press Ctrl+P to probe\n"
            "3. Click Export TXT to save\n"
            "Shows probed point + body max/min"
        )
        self.info.setStyleSheet("color: #555; padding: 5px;")
        layout.addWidget(self.info)

        self.status = QtWidgets.QLabel("Ready")
        self.status.setStyleSheet("color: green; font-weight: bold; padding: 5px;")
        layout.addWidget(self.status)

        self.result_text = QtWidgets.QTextEdit()
        self.result_text.setReadOnly(True)
        self.result_text.setPlaceholderText("Stress results appear here...")
        self.result_text.setStyleSheet("font-family: Consolas, monospace; font-size: 12px;")
        layout.addWidget(self.result_text)

        btn_layout = QtWidgets.QHBoxLayout()

        self.btn_probe = QtWidgets.QPushButton("Probe (Ctrl+P)")
        self.btn_probe.setStyleSheet("font-weight: bold; padding: 10px; font-size: 14px;")
        self.btn_probe.clicked.connect(_run_probe)
        btn_layout.addWidget(self.btn_probe)

        self.btn_remove = QtWidgets.QPushButton("Remove All")
        self.btn_remove.setStyleSheet("padding: 10px; font-size: 14px;")
        self.btn_remove.clicked.connect(self.do_remove)
        btn_layout.addWidget(self.btn_remove)

        self.btn_help = QtWidgets.QPushButton("?")
        self.btn_help.setStyleSheet("padding: 10px; font-size: 14px; font-weight: bold;")
        self.btn_help.setFixedWidth(40)
        self.btn_help.clicked.connect(self.do_help)
        btn_layout.addWidget(self.btn_help)

        layout.addLayout(btn_layout)

        btn_layout2 = QtWidgets.QHBoxLayout()

        self.btn_export = QtWidgets.QPushButton("Export TXT")
        self.btn_export.setStyleSheet("padding: 8px; font-size: 12px;")
        self.btn_export.clicked.connect(self.do_export)
        btn_layout2.addWidget(self.btn_export)

        layout.addLayout(btn_layout2)

        offset_group = QtWidgets.QGroupBox("Label Offset")
        offset_layout = QtWidgets.QHBoxLayout(offset_group)

        self.spin_x = QtWidgets.QDoubleSpinBox()
        self.spin_x.setRange(-100.0, 100.0)
        self.spin_x.setValue(2.0)
        self.spin_x.setSingleStep(0.5)
        self.spin_x.setSuffix(" X")
        offset_layout.addWidget(self.spin_x)

        self.spin_y = QtWidgets.QDoubleSpinBox()
        self.spin_y.setRange(-100.0, 100.0)
        self.spin_y.setValue(1.5)
        self.spin_y.setSingleStep(0.5)
        self.spin_y.setSuffix(" Y")
        offset_layout.addWidget(self.spin_y)

        self.spin_z = QtWidgets.QDoubleSpinBox()
        self.spin_z.setRange(-100.0, 100.0)
        self.spin_z.setValue(0.0)
        self.spin_z.setSingleStep(0.5)
        self.spin_z.setSuffix(" Z")
        offset_layout.addWidget(self.spin_z)

        layout.addWidget(offset_group)

    def do_remove(self):
        n1 = cleanup()
        n2 = cleanup_old()
        total = n1 + n2
        self.status.setText("Removed {} marker(s)".format(total))
        self.status.setStyleSheet("color: gray; font-weight: bold;")
        self.result_text.clear()

    def do_help(self):
        QtWidgets.QMessageBox.information(self.form, "Stress Probe Help",
            "STRESS PROBE MACRO\n\n"
            "HOW TO USE:\n"
            "  1. Run: Macro > Macros > StressProbe > Run\n"
            "  2. Select a vertex, edge, or face\n"
            "  3. Press Ctrl+P to probe\n"
            "  4. Click 'Export TXT' to save results\n\n"
            "WHAT IT SHOWS:\n"
            "  - Red spheres: max values on the body\n"
            "  - Blue spheres: min values on the body\n"
            "  - Green sphere: probed point (if selected)\n\n"
            "LABEL OFFSET:\n"
            "  Adjust X, Y, Z spin boxes before probing to\n"
            "  change where the text labels appear.\n\n"
            "EXPORT TXT:\n"
            "  Each click saves results in a Condition folder\n"
            "  (Condition 1, Condition 2, etc.) with force\n"
            "  values and stress results for comparison.\n\n"
            "AFTER CLOSING:\n"
            "  - All condition folders remain in the document\n"
            "  - To move a label: select it > right-click > Transform\n"
            "  - Or edit Placement > Position in the Property panel\n\n"
            "REQUIREMENTS:\n"
            "  - FEM analysis with results (CCX_Results) must exist\n"
        )

    def do_export(self):
        doc = FreeCAD.ActiveDocument
        if doc is None:
            self.status.setText("No active document")
            self.status.setStyleSheet("color: red; font-weight: bold;")
            return

        text = self.result_text.toPlainText()
        if not text.strip():
            self.status.setText("No results to export. Probe first.")
            self.status.setStyleSheet("color: orange; font-weight: bold;")
            return

        cond_num = next_condition_number()
        cond_label = "Condition {}".format(cond_num)
        cond_folder = PREFIX + cond_label.replace(" ", "_")

        grp = doc.addObject("App::DocumentObjectGroup", cond_folder)

        conds_text = get_conditions_text()

        full_text = cond_label + "\n"
        full_text += "=" * 50 + "\n\n"
        full_text += conds_text + "\n\n"
        full_text += "STRESS RESULTS\n"
        full_text += "-" * 50 + "\n\n"
        full_text += text
        full_text += "\n\n" + "=" * 50 + "\n"
        full_text += "Exported by StressProbe macro\n"

        txt_obj = doc.addObject("App::TextDocument", PREFIX + "Results_{:02d}".format(cond_num))
        txt_obj.Label = "{} - Results".format(cond_label)
        txt_obj.Text = full_text
        grp.addObject(txt_obj)

        live_grp = doc.getObject(GROUP_NAME)
        if live_grp:
            for obj in list(live_grp.Group):
                grp.addObject(obj)
            doc.removeObject(live_grp.Name)

        for obj in list(doc.Objects):
            if obj.Name.startswith(PREFIX):
                if obj == grp or obj == txt_obj:
                    continue
                if obj.TypeId == "App::DocumentObjectGroup" and obj.Name.startswith(PREFIX + "Condition"):
                    continue
                in_condition = False
                for cg in doc.Objects:
                    if cg.TypeId == "App::DocumentObjectGroup" and cg.Name.startswith(PREFIX + "Condition"):
                        if obj in cg.Group:
                            in_condition = True
                            break
                if not in_condition:
                    try:
                        grp.addObject(obj)
                    except Exception:
                        pass

        doc.recompute()
        self.status.setText("Exported as {}".format(cond_label))
        self.status.setStyleSheet("color: green; font-weight: bold;")

    def accept(self):
        FreeCADGui.Control.closeDialog()

    def reject(self):
        FreeCADGui.Control.closeDialog()


cleanup_old()
cleanup()
try:
    FreeCADGui.Control.closeDialog()
except Exception:
    pass
_panel = StressProbeTaskPanel()
FreeCADGui.Control.showDialog(_panel)
